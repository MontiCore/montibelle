enum def ActionEnum {
  enum Bob_plus_Eve_request_Camera_accepts;
  enum Alice_plus_Eve_request_Camera_accepts;
  enum Bob_plus_Eve_request_Camera_denies;
  enum Alice_plus_Eve_request_Camera_denies;
  enum Bob_without_Eve_request_Camera_accepts;
  enum Alice_without_Eve_request_Camera_accepts;
  enum Bob_without_Eve_request_Camera_denies;
  enum Alice_without_Eve_request_Camera_denies;
  enum Bob_wants_to_exit_cockpit;
  enum Alice_wants_to_exit_cockpit;
}
